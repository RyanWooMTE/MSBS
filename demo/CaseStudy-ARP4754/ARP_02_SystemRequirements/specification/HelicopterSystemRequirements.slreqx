# HelicopterSystemRequirements

## HelicopterSystemRequirements: Helicopter Flight Control System Requirements (Container)

### Introduction (Informational)
This document provides the system level requirements for a helicopter flight control system that provides attitude and attitude rate control based on pilot input commands.

### System Description (Informational)
The flight control system consists of pilot input controls, cyclic and pedals, a flight control computer and hydraulic actuators to control the main and tail rotors. A diagram of the system is shown in the figure below.
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The cyclic controls the pitch of the rotor blades to allow the helicopter pitch up or down and roll right or left. The pedal input controls the tail rotor to allow the helicopter to yaw right or left. This control system does not include throttle control or collective control, which combined control the total lift of the helicopter.

### System Requirements (Container)
This section provides the system level requirements for the flight control system. Each requirement is tagged with SR_ and a unique number for the purposes of providing trace anchors for the high-level software requirements and system verification cases to trace to. Each requirement is also put into a subsection of this section.

#### SR_1: Pilot Input Signals (Functional)
The flight control system shall process three LVDT inputs from the pilot cockpit controls, including fore/aft cyclic position, left/right cyclic position and pedal left/right position.

#### SR_2: Hydraulic Actuator Interfaces (Functional)
The flight control system shall interface to three hydraulic actuators, two for cyclic control and one for tail rotor control.

#### SR_3: Hydraulic Actuator Signals (Functional)
Each hydraulic actuator interface shall consist of an electro-hydraulic valve to control the actuator and an LVDT feedback signal providing the piston position.

#### SR_4: Hydraulic Actuator Control Loop Performance (Functional)
The flight control system shall control the hydraulic actuator position with a minimum bandwidth of 10Hz and a minimum damping of 0.4. The steady state error tracking shall be within 5% of the position command.

#### SR_5: Attitude Heading Reference System Interfaces (Functional)
The flight control system shall process three MIL1553 digital bus inputs from Attitude/Heading Reference Systems (AHRS), including pitch attitude, roll attitude, pitch rate, roll rate and yaw rate.

#### SR_6: Attitude Rate Tracking Performance (Functional)
The control system shall track set point changes in theta and phi within 1 degree steady-state error, rise time of 2 seconds (+/-0.5), maximum of 10% overshoot. The control system shall track set point changes in r within 0.5 degree/sec steady-state error, rise time of 2 seconds (+/-0.5), maximum of 10% overshoot.

#### SR_7: Control Bandwidth (Functional)
The control bandwidth shall be limited to 40 rad/sec in order to guard against high-frequency rotor dynamics and measurement noise.

#### SR_8: Control Gain and Phase Margins (Functional)
The gain margin shall be a minimum of 10db and the phase margin shall be a minimum of 45 degrees in all axes.

#### SR_9: Attitude Rate Authority Limiting (Functional)
The flight control system shall limit the pitch and roll attitudes to 30 degrees, +/-10%. The yaw rate shall be limited to 15 degrees/sec +/- 10%.

#### SR_10: Sensor Validation (Functional)
The flight control system shall determine the validity of each of the three AHRS prior to using the data from them.

#### SR_11: Sensor Voting (Functional)
When all three AHRS sensors are indicating valid, the flight control system shall use the middle value for each of the individual parameters.
When only two AHRS sensors are indicating valid, the flight control system shall use the average of the individual parameter values from the two valid AHRS.
When only one AHRS is indicating valid, the flight control system shall use the individual parameter values from that valid AHRS.
