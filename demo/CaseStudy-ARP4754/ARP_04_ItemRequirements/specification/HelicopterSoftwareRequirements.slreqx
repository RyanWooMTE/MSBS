# HelicopterSoftwareRequirements

## HelicopterSoftwareRequirements: Imported from HelicopterSoftwareRequirements.docx (Container)

### Introduction (Informational)
This document provides the high level software requirements for a helicopter flight control system that provides attitude and attitude rate control based on pilot input commands.

### System Description (Informational)
The flight control system consists of pilot input controls, cyclic and pedals, a flight control computer and hydraulic actuators to control the main and tail rotors. A diagram of the system is shown in the figure below.
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The cyclic controls the pitch of the rotor blades to allow the helicopter pitch up or down and roll right or left. The pedal input controls the tail rotor to allow the helicopter to yaw right or left. This control system does not include throttle control or collective control, which combined control the total lift of the helicopter.
This document defines the high-level software requirements for the Flight Control Computer.

### High-Level Software Requirements (Container)
This section provides the high level requirements for the flight control computer software. Each requirement is tagged with HLR_ and a unique number for the purposes of providing trace anchors for the software design and software verification cases to trace to. Each requirement is also put into a subsection of this section.

#### HLR_1: Pilot Input Signal Processing (Functional)
The flight control computer hardware processes three LVDT inputs from the pilot cockpit controls, including fore/aft cyclic position, left/right cyclic position and pedal left/right position. The hardware provides a 16 bit signed integer input to the software for each of the LVDT positions.
The characteristics of the LVDT inputs to the software are defined in the following table along with the desired command of the system.
| Signal | LVDT Input Sign | LVDT Input Range | Software Input Range | Pilot Command Scaling |
| --- | --- | --- | --- | --- |
| Fore/aft cyclic | Aft = + | +/- 2 inches | -32768 to +32767 | 15 deg/inch |
| Left/right cyclic | Right = + | +/- 2 inches | -32768 to +32767 | 15 deg/inch |
| Left/right pedal | Right = + | +/- 3 inches | -32768 to +32767 | 5 deg/sec/inch |

#### HLR_2: Hydraulic Actuator Feedback (Functional)
The flight control computer hardware processes three LVDT inputs from the hydraulic actuators, including fore/aft main rotor control, left/right main rotor control and left/right tail rotor control. The hardware provides a 16 bit signed integer input to the software for each of the LVDT positions.
The characteristics of the LVDT inputs to the software are defined in the following table along with the desired command of the system.
| Signal | LVDT Input Sign | LVDT Input Range | Software Input Range |
| --- | --- | --- | --- |
| Fore/aft main rotor feedback | Aft = + | +/- 0.1 meter | -32768 to +32767 |
| Left/right main rotor feedback | Right = + | +/- 0.1 meter | -32768 to +32767 |
| Left/right tail rotor feedback | Right = + | +/- 0.1 meter | -32768 to +32767 |

#### HLR_3: Hydraulic Actuator Drive (Functional)
The flight control computer software shall drive three electrohydraulic valve (EHV) outputs, one to each of the hydraulic actuators. The software provides a 16 bit signed integer input to the hardware for each of the electrohydraulic valve commands.
The characteristics of the EHV commands to the hardware are defined in the following table along with the desired command of the system.
| Signal | EHV Input Sign | EHV Input Range | Software Output Range |
| --- | --- | --- | --- |
| Fore/aft main rotor command | Aft = + | +/- 0.1 meter | -32768 to +32767 |
| Left/right main rotor command | Right = + | +/- 0.1 meter | -32768 to +32767 |
| Left/right tail rotor command | Right = + | +/- 0.1 meter | -32768 to +32767 |

#### HLR_4: Hydraulic Actuator Loop Control (Functional)
Each hydraulic actuator loop shall be implemented as a proportional/integral/derivative (PID) control loop operating at 1 millisecond frame rate.
The proportional gain shall be 0.135.
The integral gain shall be 0.00122.
The derivative gain shall be -0.00134.
The derivative filter coefficient shall be 0.0157

#### HLR_5: Multi-Variable Inner Loop Control (Functional)
The flight control computer software shall provide closed loop control of pitch rate, roll rate and yaw rate with a bandwidth of 40 rad/sec. The input variables from the AHRS sensor for computing the feedback signals shall be pitch attitude, roll attitude, yaw body rate, roll body rate and pitch body rate. The input variables from the outer loop control shall be pitch rate command, roll rate command and yaw rate command.
The following gain matrix shall be used to convert the AHRS input signal vector (5x1) to the proper feedback vector (1x3) for closing the loop:
2.353000 -0.356200 -0.001917 0.810900 -0.020760
-0.155700 -1.130000 0.041700 -0.045840 -0.103100
-0.027880 -0.012280 -2.011000 -0.036790 0.021030
The inner loop control shall operate at a 10miilisecond frame rate.

#### HLR_6: Pitch Outer Loop Control (Functional)
The pitch outer loop shall be implemented as a proportional/integral (PI) control loop operating at 10 millisecond frame rate.
The proportional gain shall be 1.1.
The integral gain shall be 2.2.

#### HLR_7: Roll Outer Loop Control (Functional)
The roll outer loop shall be implemented as a proportional/integral (PI) control loop operating at 10 millisecond frame rate.
The proportional gain shall be -0.0928
The integral gain shall be -1.21.

#### HLR_8: Yaw Outer Loop Control (Functional)
The yaw outer loop shall be implemented as a proportional/integral (PI) control loop operating at 10 millisecond frame rate.
The proportional gain shall be 0.131.
The integral gain shall be -2.3.

#### HLR_9: AHRS Validity Check (Functional)
Prior to using the data from an AHRS, the flight control software shall verify the AHRS data is valid.

#### HLR_10: AHRS Input Signal Processing (Functional)
The flight control computer hardware processes three AHRS digital bus inputs.
The characteristics of the AHRS inputs, from each of the three sensors, to the software are defined in the following table.
| Signal | Input Sign | Input Range |
| --- | --- | --- |
| AHRS Valid | N/A | 1 = Valid 0 = Invalid |
| Pitch Attitude | Up = + | +/- 90 degrees |
| Roll Attitude | Right = + | +/- 180 degrees |
| Pitch body rate | Up = + | +/- 60 deg/sec |
| Roll body rate | Right = + | +/- 60 deg/sec |
| Yaw body rate | Right = + | +/- 60 deg/sec |

#### HLR_11: AHRS Voting for Triple Sensors (Functional)
When three AHRS are valid, the flight control computer shall use the middle value of the three sensors for each of the individual parameters from the AHRS.

#### HLR_12: AHRS Voting for Dual Sensors (Functional)
When only two AHRS are valid, the flight control computer shall use the average of the two sensors for each of the individual parameters from the AHRS.

#### HLR_13: AHRS Usage of Single Sensor (Functional)
When only one AHRS is valid, the flight control computer shall use the individual parameters from that AHRS.
